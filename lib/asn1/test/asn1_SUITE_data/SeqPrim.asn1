SeqPrim DEFINITIONS IMPLICIT TAGS ::= 

BEGIN


Seq ::=  SEQUENCE 
{
  bool  BOOLEAN,
  boolCon [20] BOOLEAN,
  boolPri [PRIVATE 21] BOOLEAN,
  boolApp  [APPLICATION 22] BOOLEAN,
  boolExpCon [30] EXPLICIT BOOLEAN,
  boolExpPri [PRIVATE 31] EXPLICIT BOOLEAN,
  boolExpApp  [APPLICATION 32] EXPLICIT BOOLEAN
}

Empty ::= SEQUENCE {}

SeqEnum ::= SEQUENCE {
    e ENUMERATED { true },
    i INTEGER (0..63)
}

SeqEnumExt ::= SEQUENCE {
    e ENUMERATED { true, ..., false },
    i INTEGER (0..31)
}

END
