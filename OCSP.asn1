-- ocsp definition from RFC6960, 1998 Syntax

OCSP {
   iso(1) identified-organization(3) dod(6) internet(1)
   security(5) mechanisms(5) pkix(7) id-mod(0)
   id-mod-ocsp-2013-88(81)
}

DEFINITIONS EXPLICIT TAGS ::=

BEGIN

ResponseData ::= SEQUENCE {
   version             [0] EXPLICIT Version DEFAULT v1,
--   strange                 INTEGER,
   responderID            ResponderID
--   whatever              INTEGER,
--   producedAt              GeneralizedTime
}

ResponderID ::= CHOICE {
   byName              [1] Name,
   byKey               [2] KeyHash }

KeyHash ::= OCTET STRING
Name ::= CHOICE {
      rdnSequence  RDNSequence
}

RDNSequence ::= SEQUENCE OF INTEGER

Cert ::= SEQUENCE {
   id BIT STRING
}

BasicOCSPResponse ::= SEQUENCE {
  version          [0] EXPLICIT Version DEFAULT v1,
  certs            [1] EXPLICIT SEQUENCE OF Cert OPTIONAL
}

Version ::= INTEGER { v1(0) }

END
